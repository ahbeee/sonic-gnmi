module sonic-tc-dscp-map {

    yang-version 1.1;

    namespace "http://github.com/sonic-net/sonic-tc-dscp-map";

    prefix tcdscpm;

    import sonic-types {
        prefix stypes;
    }

    organization
        "SONiC";

    contact
        "SONiC";

    description
        "TC_TO_DSCP_MAP yang Module for SONiC OS";

    revision 2024-03-06 {
        description
            "Initial revision.";
    }

    container sonic-tc-dscp-map {

        container TC_TO_DSCP_MAP {

            description "TC_TO_DSCP_MAP part of config_db.json";

            list TC_TO_DSCP_MAP_LIST {

                key "name";

                leaf name {
                    type string {
                        pattern '[a-zA-Z0-9]{1}([-a-zA-Z0-9_]{0,31})';
                        length 1..32 {
                            error-message "Invalid length for map name.";
                            error-app-tag map-name-invalid-length;
                        }
                    }
                }

                list TC_TO_DSCP_MAP { //this is list inside list for storing mapping between two fields

                    key "tc";

                    leaf tc {
                        type stypes:tc_type;
                    }

                    leaf dscp {
                        type string {
                            pattern "6[0-3]|[1-5][0-9]?|[0-9]?" {
                                error-message "Invalid DSCP";
                                error-app-tag dscp-invalid;
                            }
                        }
                    }
                }
            }
        }
    }
}
