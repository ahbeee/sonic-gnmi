module sonic-dhcp-snp {
    namespace "http://github.com/Azure/sonic-dhcp-snp";
    prefix sdhcpsnp;
    yang-version 1.1;

    import sonic-vlan {
        prefix svlan;
    }

    import sonic-port {
        prefix prt;
    }

    description
        "SONIC DHCP SNOOPING";

    revision 2020-01-15 {
        description
            "Initial revision.";
    }

    container sonic-dhcp-snp {

        container DHCPSNP_GLOBAL {
            description
                "Configures global DHCP snooping";
            leaf IPv4 {
                type string {
                    pattern 'disable|enable';
                }
                default "disable";
            }
        }

        container DHCPSNP_VLAN {
            description
                "Configures VLAN DHCP snooping";
            list DHCPSNP_VLAN_LIST {
                key "vlan-name";

                leaf vlan-name {
                    type leafref {
                        path "/svlan:sonic-vlan/svlan:VLAN/svlan:VLAN_LIST/svlan:name";
                    }
                }

                leaf IPv4 {
                    type string {
                        pattern 'disable|enable';
                    }
                    default "enable";
                }
            }
        }

        container DHCPSNP_TRUST {
            description
                "Configures trusted ports";
            list DHCPSNP_TRUST_LIST {
                key "port_name";

                leaf port_name {
                    type string {
                        pattern "Ethernet([1-3][0-9]{3}|[1-9][0-9]{2}|[1-9][0-9]|[0-9])";
                    }
                }

                leaf trust {
                    type string {
                        pattern 'disable|enable';
                    }
                    default "enable";
                }
            }
        }
    }
}
