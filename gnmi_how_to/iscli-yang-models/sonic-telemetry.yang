module sonic-telemetry {

    yang-version 1.1;

    namespace "http://github.com/sonic-net/sonic-telemetry";
    prefix telemetry;

    import ietf-inet-types {
        prefix inet;
    }
    import sonic-vrf {
        prefix vrf;
    }
    import sonic-mgmt_vrf {
        prefix mvrf;
    }


    organization
        "SONiC";

    contact
        "SONiC";

    description "TELEMETRY YANG Module for SONiC OS";

    revision 2025-09-01 {
        description "Add VRF support for Telemetry service";
    }
    revision 2022-05-13 {
        description "First Revision";
    }

    typedef vrf-device {
        description "Represents GNMI VRF device";
        type enumeration {
            enum default;
            enum mgmt;
        }
    }

    container sonic-telemetry {

        container TELEMETRY {

            description "TELEMETRY TABLE part of config_db.json";

            container certs {

                leaf ca_crt {
                    type string {
                        pattern '(/[a-zA-Z0-9_-]+)*/([a-zA-Z0-9_-]+).cer|';
                    }
                    description "Local path for ca_crt.";
                }

                leaf server_crt {
                    type string {
                        pattern '(/[a-zA-Z0-9_-]+)*/([a-zA-Z0-9_-]+).cer|';
                    }
                    description "Local path for server_crt.";
                }

                leaf server_key {
                    type string {
                        pattern '(/[a-zA-Z0-9_-]+)*/([a-zA-Z0-9_-]+).key|';
                    }
                    description "Local path for server_key.";
                }

            }

            container gnmi {

                leaf client_auth {
                    type boolean;
                    description "Flag for requiring client auth.";
                }

                leaf log_level {
                    type uint8 {
                        range 0..100;
                    }
                    description "Log level for gnmi.";
                }

                leaf port {
                    type inet:port-number;
                    description "Port gnmi runs on.";
                }

                leaf vrf {
                    type union {
                        type leafref {
                            path "/vrf:sonic-vrf/vrf:VRF/vrf:VRF_LIST/vrf:name";
                        }
                        type vrf-device;
                    }
                    must "(current() != 'mgmt')
                    or (/mvrf:sonic-mgmt_vrf/mvrf:MGMT_VRF_CONFIG/mvrf:vrf_global/mvrf:mgmtVrfEnabled = 'true')";
                    description "VRF for Telemetry.";
                }

            }

        }
    }
}
