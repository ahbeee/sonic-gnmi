module sonic-port {
	namespace "http://github.com/Azure/sonic-port";
	prefix prt;

	import sonic-common {
		prefix cmn;
	}

	import sonic-extension {
		prefix sonic-ext;
	}

	import ietf-yang-types {
		prefix yang;
	}

	organization
		"SONiC";

	contact
		"SONiC";

	description
		"SONIC VLAN";

	revision 2019-05-15 {
		description
			"Initial revision.";
	}


	container sonic-port {

		container PORT {

			list PORT_LIST {
				key "ifname";

				leaf ifname {
					type string {
						pattern "Ethernet([1-3][0-9]{3}|[1-9][0-9]{2}|[1-9][0-9]|[0-9])" {
							error-message "Invalid interface name";
							error-app-tag interface-name-invalid;
						}
					}
				}

				leaf index {
					type uint16;
					mandatory true;

				}

				leaf parent_port {
					type string {
						pattern "Ethernet([1-3][0-9]{3}|[1-9][0-9]{2}|[1-9][0-9]|[0-9])" {
							error-message "Invalid interface name";
							error-app-tag interface-name-invalid;
						}
					}
				}

				leaf speed {
					type uint64 {
						range "10|100|1000|2500|5000|10000|25000|40000|50000|100000|200000|400000|600000|800000" {
							error-message "Invalid Ethernet interface speed";
							error-app-tag port-speed-invalid;
						}
					}
					sonic-ext:custom-validation ValidatePortSpeed;
				}

				leaf valid_speeds {
					type string;
				}

				leaf alias {
					type string {
						pattern '[ -~]{0,64}';
					}
				}

				leaf description {
					type string {
						pattern '[ -~]{0,64}';
					}
				}

				leaf mtu {
					type uint32 {
						range "1312..9216" {
							error-message "Invalid MTU value";
							error-app-tag mtu-invalid;
						}
					}
					default 9100;
					must "not(../mtu_slowpath) or (. >= ../mtu_slowpath)" {
							error-message "Interface MTU value should be greater than or equal to slowpath MTU value";
							error-app-tag mtu-invalid;
					}
					sonic-ext:custom-validation ValidateMtu;
				}

				leaf mtu_slowpath {
					description "The interface slowpath MTU value";
					type uint32 {
						range "68..9216" {
							error-message "Invalid slow path MTU value";
							error-app-tag slowpath-mtu-invalid;
						}
					}
					must "not(../mtu) or (. <= ../mtu)" {
							error-message "Interface slowpath MTU value should be smaller than or equal to MTU value";
							error-app-tag slowpath-mtu-invalid;
					}
					sonic-ext:custom-validation ValidateSlowpathMtu;
				}

				leaf lanes {
					type string;
					mandatory true;
				}

				leaf admin_status {
					type cmn:admin-status;
					default "down";
				}

				leaf link_training {
					description "Port link training mode";
					type cmn:on-off-status;
					sonic-ext:custom-validation ValidateLinkTraining;
				}

				leaf autoneg {
					type cmn:on-off-status;
					default "off";
				}

				leaf-list adv_speeds {
					description "Port advertised speeds, valid value could be a list of interger or all";

					type union {
						type uint32 {
							range 1..800000;
						}
						type string {
							pattern "all";
						}
					}
					sonic-ext:custom-validation ValidatePortAdvSpeed;
				}

				must "(count(adv_speeds[text()='all']) = 0) or (count(adv_speeds) = 1)";

				leaf subport {
					description "Logical subport(s) for physical port breakout";
					type uint8 {
						range 0..8;
					}
				}

				leaf asic_port_name {
					type string;
					description "port name in asic and asic name, e.g Eth0-ASIC1";
				}

				leaf role {
					type string {
						pattern "Ext|Int|Inb|Rec";
					}
					description "Internal port or External port for multi-asic platform";
					default "Ext";
				}

				leaf fec {
					type string {
						pattern "rs|fc|none";
					}
				}

				leaf pfc_asym {
					type string {
						pattern "on|off";
					}
				}

				leaf tpid {
					description "This leaf describes the possible TPID value that can be configured
							to the specified port if the HW supports TPID configuration. The possible
							values are 0x8100, 0x9100, 0x9200, 0x88a8, and 0x88A8";
					type string {
						pattern "0x8100|0x9100|0x9200|0x88a8|0x88A8" {
							error-message "Only allowed: 0x8100, 0x9100, 0x9200, or 0x88A8";
							error-app-tag tpid-invalid;
						}
					}
					sonic-ext:custom-validation ValidateTpid;
				}

				leaf mux_cable {
					type boolean;
				}

				leaf tx_power {
					description "Target output power(dBm) for the 400G ZR transceiver";
					type decimal64 {
						fraction-digits 1;
					}
					sonic-ext:custom-validation ValidateTxPower;
				}

				leaf laser_freq {
					description "Target laser frequency(GHz) for the 400G ZR transceiver";
					type int32;
					must ". > 0" {
						error-message "Invalid frequency, it must be > 0";
					}
					sonic-ext:custom-validation ValidateLaserFreq;
				}

				leaf grid_space {
					description "Target grid space(GHz) for the 400G ZR transceiver";
					type uint16 {
						range "75|100" {
							error-message "Invalid grid space, it must be 75 or 100 GHz";
						}
					}
					sonic-ext:custom-validation ValidateGridSpace;
				}

				leaf application_code {
					description "The part number and the target application code for the CMIS transceiver or auto";
					must "(current() = 'auto') or contains(current(), ':')";
					type string {
						length 1..32;
					}
					sonic-ext:custom-validation ValidateAppCode;
				}

				leaf pms_enable {
					description "Enable/Disable PMS";
					type string {
						pattern "yes|no";
					}
					sonic-ext:custom-validation ValidatePMSenable;
				}

				leaf pms_maximum {
					description "Set the maximum number of allowed MAC addresses on a port";
					type uint16 {
						range "1..4097" {
							error-message "Invalid value";
						}
					}
					default 1;
					sonic-ext:custom-validation ValidatePMSmaximum;
				}

				leaf pms_violation {
					description "PMS violation action (\"Protect\"/\"Restrict\"/\"Shutdown\")";
					type string {
						pattern "protect|restrict|shutdown";
					}
					default "protect";
					sonic-ext:custom-validation ValidatePMSviolation;
				}

				leaf flow_control {
					type string {
						pattern "tx|rx|both|none";
					}
					sonic-ext:custom-validation ValidateGFC;
				}
			}
		}

		container PORT_TABLE {
			config false;
			sonic-ext:db-name "STATE_DB";
			sonic-ext:key-delim "|";

			list PORT_TABLE_LIST {
				key "ifname";

				leaf ifname {
					type leafref {
						path "../../../PORT/PORT_LIST/ifname";
					}
				}

				leaf netdev_oper_status {
					type cmn:oper-status;
					default "down";
				}

				leaf speed {
					type uint64 {
						range "0|1000|10000|25000|40000|50000|100000|200000|400000|600000|800000" {
							error-message "Invalid Ethernet interface speed";
							error-app-tag port-speed-invalid;
						}
					}
				}

				leaf supported_speeds {
					description "port supported speeds";
					type string;
				}
			}
		}
	}
}
