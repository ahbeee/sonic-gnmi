module sonic-xstp {
    namespace "http://github.com/Azure/sonic-xstp";
    prefix sxstp;
    yang-version 1.1;

    import ietf-inet-types {
        prefix inet;
    }

    import sonic-port {
        prefix prt;
    }

    import sonic-portchannel {
        prefix spc;
    }

    import sonic-extension {
        prefix sonic-ext;
    }

    organization
        "SONiC";

    contact
        "SONiC";

    description
        "SONIC XSTP";

    revision 2019-07-02 {
        description
            "Initial revision.";
    }

    container sonic-xstp {

        container XSTP_GLOBAL {
            list XSTP_GLOBAL_LIST {
                key "param";

                leaf param {
                    type string;
                    sonic-ext:custom-validation ValidateXstpGlobalValue;
                }

                leaf value {
                    type string;
                    sonic-ext:custom-validation ValidateXstpGlobalDisable;
                }
            }
        }


        container XSTP_MST_GLOBAL {
            list XSTP_MST_GLOBAL_LIST {
                key "param";
                sonic-ext:custom-validation ValidateXstpMstpModeCheck;
                leaf param {
                    type string;
                }

                leaf value {
                    type string;
                    sonic-ext:custom-validation ValidateXstpGlobalDisable;
                }
            }
        }

        container XSTP_MST {
            list XSTP_MST_LIST {
                key "mstid";
                max-elements 32;

                leaf mstid {
                    mandatory true;
                    type uint16 {
                        range "0..4094" {
                            error-message "MST instance ID must be in range 0-4094.";
                            error-app-tag instance-id-invalid;
                        }
                    }
                }

                leaf vlan_str{
                    type string;
                    sonic-ext:custom-validation ValidateMstVlanStr;
                }

                leaf priority {
                    type uint32 {
                        range "0|4096|8192|12288|16384|20480|24576|28672|32768|36864|40960|45056|49152|53248|57344|61440" {
                            error-message "MST bridge priority of a spanning tree instance must be in range 0-61440.";
                            error-app-tag  mst-priority-invalid;
                        }
                    }
                    sonic-ext:custom-validation ValidateXstpMstPri;
                }
            }
        }

        container XSTP_INTERFACE {
            list XSTP_INTERFACE_LIST {
                key "ifname";
                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    sonic-ext:custom-validation ValidateXstpIntfCheck;
                }

                leaf bpdu-filter {
                    type enumeration {
                        enum enabled;
                        enum disabled;
                    }
                    sonic-ext:custom-validation ValidateXstpIntfBpduFilterCheck;
                }

                leaf bpdu-guard {
                    type enumeration {
                        enum enabled;
                        enum disabled;
                    }
                    sonic-ext:custom-validation ValidateXstpIntfBpduGuardCheck;
                }

                leaf auto-recovery {
                    type enumeration {
                        enum enabled;
                        enum disabled;
                    }
                }

                leaf auto-recovery-interval {
                    type uint32 {
                        range "30..86400" {
                            error-message "BPDU guard auto-recovery value must be in range 30-84600.";
                            error-app-tag  auto-recovery-interval-invalid;
                        }
                    }
                }

                leaf root-guard {
                    type enumeration {
                        enum enabled;
                        enum disabled;
                    }
                    sonic-ext:custom-validation ValidateXstpIntfRootGuardCheck;
                }

                leaf spanning-disable {
                    type enumeration {
                        enum enabled;
                        enum disabled;
                    }
                    sonic-ext:custom-validation ValidateXstpIntfSpanningDisableCheck;
                }

                leaf edge-port {
                    type enumeration {
                        enum auto;
                        enum false;
                        enum true;
                    }
                    sonic-ext:custom-validation ValidateXstpIntfEdgePortCheck;
                }

                leaf cost {
                    type uint32 {
                        range "1..200000000" {
                            error-message "Interface cost must be in range 1-200000000";
                            error-app-tag  interface-priority-invalid;
                        }
                    }
                    sonic-ext:custom-validation ValidateXstpIntfCostCheck;
                }

                leaf port-priority {
                    type uint32 {
                        range "0|16|32|48|64|80|96|112|128|144|160|176|192|208|224|240" {
                            error-message "Interface bridge priority must be in range 0-240";
                            error-app-tag  port-priority-invalid;
                        }
                    }
                    sonic-ext:custom-validation ValidateXstpIntfPortPriorityCheck;
                }

                leaf loopback-detection {
                    type enumeration {
                        enum enabled;
                        enum disabled;
                    }
                    sonic-ext:custom-validation ValidateXstpIntfLBDCheck;
                }

                leaf lbd-action {
                    type enumeration {
                        enum block;
                        enum shutdown;
                    }
                    sonic-ext:custom-validation ValidateXstpIntfLBDActionCheck;
                }

                leaf lbd-shutdown-interval {
                    type uint32 {
                        range "60..86400" {
                            error-message "The interval must be in range 60-86400.";
                            error-app-tag  lbd-shutdown-interval-invalid;
                        }
                    }
                    sonic-ext:custom-validation ValidateXstpIntfLBDActionCheck;
                }
            }
        }

        container XSTP_MST_INTERFACE {
            list XSTP_MST_INTERFACE_LIST {
                key "mstid ifname";

                leaf mstid {
                    mandatory true;
                    type uint16 {
                        range "0..4094" {
                            error-message "MST instance ID must be in range 0-4094.";
                            error-app-tag instance-id-invalid;
                        }
                    }
                    sonic-ext:custom-validation ValidateXstpMstInterfaceExist;
                }

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                        sonic-ext:custom-validation ValidateXstpIntfCheck;
                    }
                }

                leaf cost {
                    type uint32 {
                        range "1..200000000" {
                            error-message "Interface MST cost must be in range 1-200000000.";
                            error-app-tag  interface-priority-invalid;
                        }
                    }
                    sonic-ext:custom-validation ValidateXstpMstInterfaceCostCheck;
                }

                leaf port-priority {
                    type uint32 {
                        range "0|16|32|48|64|80|96|112|128|144|160|176|192|208|224|240" {
                            error-message "Interface MST bridge priority must be in range 0-240.";
                            error-app-tag  port-priority-invalid;
                        }
                    }
                    sonic-ext:custom-validation ValidateXstpMstInterfacePriCheck;
                }
            }
        }
        container STP_PORT_TABLE {
            config false;
            sonic-ext:db-name "APPL_DB";
            sonic-ext:key-delim ":";
            list STP_PORT_TABLE_LIST {
                key "ifname";

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf bpdu_guard_shutdown {
                    type enumeration {
                        enum yes;
                        enum no;
                    }
                }

                leaf LBD_shutdown {
                    type enumeration {
                        enum yes;
                        enum no;
                    }
                }
            }
        }
    }
}
