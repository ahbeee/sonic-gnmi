module sonic-tc-priority-group-map {

    yang-version 1.1;

    namespace "http://github.com/Azure/sonic-tc-priority-group-map";

    prefix tpgm;

    import sonic-extension {
        prefix sonic-ext;
    }

    organization
        "SONiC";

    contact
        "SONiC";

    description
        "TC_TO_PRIORITY_GROUP_MAP yang Module for SONiC OS";

    revision 2021-04-15 {
        description
            "Initial revision.";
    }

    container sonic-tc-priority-group-map {

        container TC_TO_PRIORITY_GROUP_MAP {

            description "TC_TO_PRIORITY_GROUP_MAP part of config_db.json";

            list TC_TO_PRIORITY_GROUP_MAP_LIST {

                key "name";
                sonic-ext:map-list "true"; //special annotation for map table
                sonic-ext:map-leaf "tc pg"; //every key:value pair is mapped to list keys, e.g. "1":"7" ==> tc=1, pg=7
                sonic-ext:custom-validation ValidateTctoPg;
                leaf name {
                    type string;
                }

                list TC_TO_PRIORITY_GROUP_MAP_INTERNAL_LIST { //this is list inside list for storing mapping between two fields

                    key "tc pg";

                    leaf tc {
                        type string {
                            pattern "[0-7]?" {
                                error-message "Invalid Traffic Class";
                                error-app-tag tc-invalid;
                            }
                        }
                    }

                    leaf pg {
                        type string {
                            pattern "[0-7]?" {
                                error-message "Invalid Priority Group";
                                error-app-tag pg-invalid;
                            }
                        }
                    }
                }
            }
        }
    }
}
