module sonic-bgp-global {
    namespace "http://github.com/Azure/sonic-bgp-global";
    prefix sbgpg;
    yang-version 1.1;

    import sonic-vrf {
        prefix svrf;
    }

    import ietf-inet-types {
        prefix inet;
    }

    import sonic-bgp-common {
        prefix sbc;
    }

    //import sonic-route-map {
    //    prefix srmap;
    //}

    import sonic-extension {
        prefix sonic-ext;
    }

    import sonic-common {
        prefix cmn;
    }

    organization
        "SONiC";

    contact
        "SONiC";

    description
        "SONIC BGP Global YANG";

    revision 2019-11-20 {
        description
            "Added BGP fields for extensive features.";
    }

    revision 2019-09-15 {
        description
            "Initial revision.";
    }

    container sonic-bgp-global {
        container BGP_GLOBALS {
            list BGP_GLOBALS_LIST {
                key "vrf_name";

                leaf vrf_name {
                    type union {
                        type string {
                            pattern "default";
                        }
                        type leafref {
                            path "/svrf:sonic-vrf/svrf:VRF/svrf:VRF_LIST/svrf:vrf_name";
                        }
                    }
                    sonic-ext:custom-validation ValidateVrfConfiguration;
                }

                leaf router_id {
                    type inet:ipv4-address;
                }

                leaf local_asn {
                    type uint32 {
                        range "1..4294967295";
                    }
                }

                leaf always_compare_med {
                    type boolean;
                }

                leaf load_balance_mp_relax {
                    type boolean;
                }

                leaf graceful_restart_enable {
                    type boolean;
                }

                leaf gr_preserve_fw_state {
                    type boolean;
                    description
                        "Set F-bit indication that FIB is preserved while doing Graceful Restart.";
                }

                leaf gr_restart_time {
                    must "(. >= 1 and . <= 3600) or (. <= 0)";
                    type int16;
                    description
                        "Set a value(<=0) to clear the time setting";
                }

                leaf gr_stale_routes_time {
                    must "(. >= 1 and . <= 3600) or (. <= 0)";
                    type int16;
                    description
                        "Set a value(<=0) to clear the time setting";
                }

                leaf external_compare_router_id {
                    type boolean;
                }

                leaf ignore_as_path_length {
                    type boolean;
                }

                leaf log_nbr_state_changes {
                    type boolean;
                }

                leaf rr_cluster_id {
                    type string;
                }

                leaf rr_allow_out_policy {
                    type boolean;
                }

                leaf disable_ebgp_connected_rt_check {
                    type boolean;
                }

                leaf fast_external_failover {
                    type boolean;
                }

                leaf network_import_check {
                    type boolean;
                }

                leaf graceful_shutdown {
                    type boolean;
                }

                leaf rr_clnt_to_clnt_reflection {
                    type boolean;
                    description
                        "Enable client to client route reflection.";
                }

                leaf max_dynamic_neighbors {
                    type uint16 {
                        range 1..5000;
                    }
                    description
                        "Maximum number of BGP dynamic neighbors that can be created.";
                }

                leaf read_quanta {
                    type uint8 {
                        range 1..10;
                    }
                    description
                        "This indicates how many packets to read from peer socket per I/O cycle";
                }

                leaf write_quanta {
                    type uint8 {
                        range 1..10;
                    }
                    description
                        "This indicates how many packets to write to peer socket per run";
                }

                leaf coalesce_time {
                    type uint32;
                    description
                        "Subgroup coalesce timer value in milli-sec";
                }

                leaf route_map_process_delay {
                    type uint16 {
                        range 0..600;
                    }
                    description
                        "0 disables the timer, no route updates happen when route-maps change";
                }

                leaf deterministic_med {
                    type boolean;
                    description
                        "Pick the best-MED path among paths advertised from the neighboring AS.";
                }

                leaf med_confed {
                    type boolean;
                    description
                        "Compare MED among confederation paths when set to true.";
                }

                leaf med_missing_as_worst {
                    type boolean;
                    description
                        "Treat missing MED as the least preferred one when set to true.";
                }

                leaf compare_confed_as_path {
                    type boolean;
                    description
                        "Compare path lengths including confederation sets & sequences in selecting a route";
                }

                leaf as_path_mp_as_set {
                    type boolean;
                    description
                        "Generate an AS_SET.";
                }

                leaf default_ipv4_unicast {
                    type boolean;
                    description
                        "Activate ipv4-unicast for a peer by default";
                }

                leaf default_local_preference {
                    type uint32;
                    description
                        "Configure default local preference value.";
                }

                leaf default_show_hostname {
                    type boolean;
                    description
                        "Show hostname in BGP dumps.";
                }

                leaf default_shutdown {
                    type boolean;
                    description
                        "Apply administrative shutdown to newly configured peers.";
                }

                leaf default_subgroup_pkt_queue_max {
                    type uint8 {
                        range 20..100;
                    }
                    description
                        "Configure subgroup packet queue max.";
                }

                leaf max_med_time {
                    type uint32{
                        range 5..86400;
                    }
                    description
                        "Time (seconds) period for max-med";
                }

                leaf max_med_val {
                    type uint32;
                    description
                        "Max MED value to be used";
                }

                leaf max_med_admin {
                    type boolean;
                    description
                        "Enable Max MED admin status.";
                }

                leaf max_med_admin_val {
                    type uint32;
                    description
                        "Administrative Max MED value to be used";
                }

                leaf max_delay {
                    type uint16 {
                        range 0..3600;
                    }
                    description
                        "Maximum delay for best path calculation.";
                }

                leaf establish_wait {
                    type uint16 {
                        range 0..3600;
                    }
                    must "(/cmn:operation/cmn:operation = 'DELETE') or (current() <= current()/../max_delay) " {
                         error-message "Maximum delay for best path calculation should not be less than updates !";
                    }
                    description
                        "Maximum delay for updates.";
                }

                leaf confed_id {
                    type sbc:bgp_asn;
                    description
                        "Set routing domain confederation AS.";
                }

                leaf-list confed_peers {
                    type sbc:bgp_asn;
                    description
                        "Peer ASs in BGP confederation";
                    sonic-ext:custom-validation ValidateConfederationPeers;
                }

                leaf keepalive {
                    type uint16;
                    description "Keepalive interval";
                }

                leaf holdtime {
                    type uint16;
                    description "Hold time";
                }

                leaf ebgp_requires_policy {
                    type boolean;
                    description
                        "Enable require policy for eBGP peers (RFC8212)";
                }
            }
        }

        container BGP_GLOBALS_AF {
            list BGP_GLOBALS_AF_LIST {
                key "vrf_name afi_safi";

                leaf vrf_name {
                    type leafref {
                        path "../../../BGP_GLOBALS/BGP_GLOBALS_LIST/vrf_name";
                    }
                }

                leaf afi_safi {
                    type string;
                }

                leaf max_ebgp_paths {
                    type uint16 {
                        range "0..256";
                    }
                }

                leaf max_ibgp_paths {
                    type uint16 {
                        range "0..256";
                    }
                }

                leaf import_vrf {
                    type union {
                        type string {
                            pattern "default";
                        }
                        type leafref {
                            path "../../../BGP_GLOBALS/BGP_GLOBALS_LIST/vrf_name";
                        }
                    }
                    must "current() != current()/../vrf_name" {
                        error-message "Import VRF should be different than self!";
                    }
                }

                leaf import_vrf_route_map {
                    type string;

                    /* Not support route-map yang yet
                    type leafref {
                        path "/srmap:sonic-route-map/srmap:ROUTE_MAP_SET/srmap:ROUTE_MAP_SET_LIST/srmap:name";
                    }
                    */
                }

                leaf route_download_filter {
                    type string;

                    /*
                    type leafref {
                        path "/srmap:sonic-route-map/srmap:ROUTE_MAP_SET/srmap:ROUTE_MAP_SET_LIST/srmap:name";
                    }
                    */
                }

                leaf ebgp_route_distance {
                    type uint8 {
                        range "0..255";
                    }
                }

                leaf ibgp_route_distance {
                    type uint8 {
                        range "0..255";
                    }
                }

                leaf local_route_distance {
                    type uint8 {
                        range "0..255";
                    }
                }

                leaf ibgp_equal_cluster_length {
                    type boolean;
                    description
                        "Match the cluster length.";
                }

                leaf route_flap_dampen {
                    must "current()/../afi_safi = 'ipv4_unicast'" { error-message "Route flap dampening is supported only for IPv4 address family!"; }
                    type boolean;
                }

                leaf route_flap_dampen_half_life {
                    must "current()/../afi_safi = 'ipv4_unicast'" { error-message "Route flap dampening is supported only for IPv4 address family!"; }
                    type uint8 {
                        range "0..45";
                    }
                }

                leaf route_flap_dampen_reuse_threshold {
                    must "current()/../afi_safi = 'ipv4_unicast'" { error-message "Route flap dampening is supported only for IPv4 address family!"; }
                    type uint16 {
                        range "0..20000";
                    }
                }

                leaf route_flap_dampen_suppress_threshold {
                    must "current()/../afi_safi = 'ipv4_unicast'" { error-message "Route flap dampening is supported only for IPv4 address family!"; }
                    type uint16 {
                        range "0..20000";
                    }
                }

                leaf route_flap_dampen_max_suppress {
                    must "current()/../afi_safi = 'ipv4_unicast'" { error-message "Route flap dampening is supported only for IPv4 address family!"; }
                    type uint8 {
                        range "0..255";
                    }
                }

                uses sbc:sonic-bgp-af-evpn-global;
            }
        }

        container BGP_GLOBALS_AF_AGGREGATE_ADDR {
            list BGP_GLOBALS_AF_AGGREGATE_ADDR_LIST {
                key "vrf_name afi_safi ip_prefix";

                leaf vrf_name {
                    type leafref {
                        path "../../../BGP_GLOBALS/BGP_GLOBALS_LIST/vrf_name";
                    }
                }

                leaf afi_safi {
                    type string;
                }

                leaf ip_prefix {
                    type inet:ip-prefix;
                }

                leaf as_set {
                    type boolean;
                }

                leaf summary_only {
                    type boolean;
                }

                leaf policy {
                    type string;

                    /* Not support route-map yang yet
                    type leafref {
                        path "/srmap:sonic-route-map/srmap:ROUTE_MAP_SET/srmap:ROUTE_MAP_SET_LIST/srmap:name";
                    }
                    */
                }

            }
        }

        container BGP_GLOBALS_AF_NETWORK {
            list BGP_GLOBALS_AF_NETWORK_LIST {
                key "vrf_name afi_safi ip_prefix";

                leaf vrf_name {
                    type leafref {
                        path "../../../BGP_GLOBALS/BGP_GLOBALS_LIST/vrf_name";
                    }
                }

                leaf afi_safi {
                    type string;
                }

                leaf ip_prefix {
                    type inet:ip-prefix;
                }

                leaf policy {
                    type string;

                    /* Not support route-map yang yet
                    type leafref {
                        path "/srmap:sonic-route-map/srmap:ROUTE_MAP_SET/srmap:ROUTE_MAP_SET_LIST/srmap:name";
                    }
                    */
                }

                leaf backdoor {
                    type boolean;
                }
            }
        }

        container BGP_GLOBALS_EVPN_RT {
            list BGP_GLOBALS_EVPN_RT_LIST {
                key "vrf afi-safi-name route-target";

                leaf vrf {
                    type string;
                }

                leaf afi-safi-name {
                    type string;
                }

                leaf route-target {
                    type string;
                }

                leaf route-target-type {
                    type string;
                }
            }
        }

        container BGP_GLOBALS_EVPN_VNI {
            list BGP_GLOBALS_EVPN_VNI_LIST {
                key "vrf afi-safi-name vni-number";

                leaf vrf {
                    type string;
                }

                leaf afi-safi-name {
                    type string;
                }

                leaf vni-number {
                    type uint32;
                }

                uses sbc:sonic-bgp-evpn-vni-common;
            }
        }

        container BGP_GLOBALS_EVPN_VNI_RT {
            list BGP_GLOBALS_EVPN_VNI_RT_LIST {
                key "vrf afi-safi-name vni-number route-target";

                leaf vrf {
                    type string;
                }

                leaf afi-safi-name {
                    type string;
                }

                leaf vni-number {
                    type uint32;
                }

                leaf route-target {
                    type string;
                }

                leaf route-target-type {
                    type string;
                }
            }
        }
    }
}
