module sonic-mgmt_port {
  yang-version 1.1;
  namespace "http://github.com/sonic-net/sonic-mgmt_port";
  prefix mgmtprt;

  import sonic-types {
    prefix stypes;
  }

  description
    "MANAGEMENT PORT yang Module for SONiC OS";

  revision 2021-04-07 {
    description
      "First Revision";
  }

  container sonic-mgmt_port {
    container MGMT_PORT {
      description
        "MANAGEMENT PORT part of config_db.json";
      list MGMT_PORT_LIST {
        key "name";
        leaf name {
          type string {
            pattern 'eth([1-3][0-9]{3}|[1-9][0-9]{2}|[1-9][0-9]|[0-9])(.[1-9][0-9]{0,2}|[1-3][0-9]{3}|40[0-8][0-9]|409[0-5])?';
          }
        }
        leaf speed {
          type uint16 {
            range "10|100|1000";
          }
          description
            "Management port speed in megabytes.";
        }
        leaf autoneg {
          type string {
            pattern 'on|off';
          }
        }
        leaf alias {
          type string;
        }
        leaf description {
          type string;
        }
        leaf mtu {
          type uint16 {
            range "1500..9216";
          }
          default "1500";
        }
        leaf admin_status {
          type stypes:admin_status;
          default "up";
        }
      }
    }
  }
}
