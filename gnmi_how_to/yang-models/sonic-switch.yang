module sonic-switch {

    yang-version 1.1;

    namespace "http://github.com/sonic-net/sonic-switch";
    prefix switch;


    description "SWITCH YANG Module for SONiC OS";

    revision 2026-01-08 {
        description "First Revision";
    }

    container sonic-switch {

        container SWITCH {

            description "SWITCH part of config_db.json";

            container switch {

                leaf fdb_aging_time {
                    type uint32 {
                        range 0..86400;
                    }
                }
                leaf ipv4_nbr_age_time {
                    type uint32 {
                        range 60..14400;
                    }
                }
                leaf ipv6_nbr_age_time {
                    type uint32 {
                        range 60..14400;
                    }
                }
            }
            /* end of container switch */
        }
        /* end of container SWITCH */
    }
    /* end of top level container */
}
