module sonic-dhcp-relay {
    namespace "http://github.com/Azure/sonic-dhcp-relay";
    prefix sdrelay;

    import ietf-inet-types {
        prefix inet;
    }

    organization
        "SONiC";

    contact
        "SONiC";

    description
        "SONIC DHCP RELAY";

    revision 2024-08-06 {
        description
            "Initial version.";
    }

    container sonic-dhcp-relay{

        container DHCP_RELAY {

            list DHCP_RELAY_LIST {
                key "name";

                leaf name {
                    type string {
                        pattern "Vlan(409[0-4]|40[0-8][0-9]|[1-3][0-9]{3}|[1-9][0-9]{2}|[1-9][0-9]|[1-9])" {
                            error-message "Invalid Vlan name pattern";
                            error-app-tag vlan-name-invalid;
                        }
                    }
                }

                leaf-list dhcpv6_servers {
                    type inet:ipv6-address;
                }
            }
        }
    }
}
