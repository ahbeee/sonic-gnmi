module sonic-breakout {
	namespace "http://github.com/Azure/sonic-breakout";
	prefix brkout;

	import sonic-extension {
		prefix sonic-ext;
	}

	import ietf-yang-types {
		prefix yang;
	}

	organization
		"SONiC";

	contact
		"SONiC";

	description
		"SONIC BREAKOUT";

	revision 2019-05-15 {
		description
			"Initial revision.";
	}


	container sonic-breakout {

		container BREAKOUT_CFG {

			list BREAKOUT_CFG_LIST {
				key "ifname";

				leaf ifname {
					type string {
						pattern "Ethernet([1-3][0-9]{3}|[1-9][0-9]{2}|[1-9][0-9]|[0-9])" {
							error-message "Invalid interface name";
							error-app-tag interface-name-invalid;
						}
					}
				}

				leaf brkout_mode {
					type string;
				}
			}
		}
	}
}
