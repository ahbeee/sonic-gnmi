module sonic-portchannel-interface {
    namespace "http://github.com/Azure/sonic-portchannel-interface";
    prefix spchint;

    import ietf-inet-types {
        prefix inet;
    }

    import sonic-portchannel {
        prefix spc;
    }

    import sonic-vrf {
        prefix vrf;
    }

    // import sonic-loopback-interface {
    //     prefix lointf;
    // }

    import sonic-common {
        prefix cmn;
    }

    import sonic-extension {
        prefix sonic-ext;
    }

    organization
        "SONiC";

    contact
        "SONiC";

    description
        "SONIC PORTCHANNEL INTERFACE";

    revision 2019-07-02 {
        description
            "Initial revision.";
    }

    revision 2019-12-01 {
        description
            "Add vrf_name for VRF interface binding.";
    }

    container sonic-portchannel-interface {

        container PORTCHANNEL_INTERFACE {

            list PORTCHANNEL_INTERFACE_LIST {
                key "pch_name";

                leaf pch_name{
                    type leafref {
                        path "/spc:sonic-portchannel/spc:PORTCHANNEL/spc:PORTCHANNEL_LIST/spc:name";
                    }
                }
                leaf nat_zone {
                    sonic-ext:custom-validation ValidateNatIntf;
                    description "NAT Zone for the portchannel interface";
                    type uint8 {
                        range "0..3" {
                            error-message "Invalid nat zone for the portchannel interface.";
                            error-app-tag nat-zone-invalid;
                        }
                    }
                }
                leaf ipv6_use_link_local_only {
                    sonic-ext:custom-validation ValidatePchInterface;
                    type enumeration {
                        enum enable;
                        enum disable;
                    }
                }
                leaf grat_arp {
                    type string {
                        pattern "enabled|disabled";
                    }
                }

                leaf vrf_name {
                    type leafref {
                        path "/vrf:sonic-vrf/vrf:VRF/vrf:VRF_LIST/vrf:vrf_name";
                    }
                }
            }
            list PORTCHANNEL_INTERFACE_IPADDR_LIST {
                key "pch_name ip_prefix";

                leaf pch_name{
                    type leafref {
                        path "/spc:sonic-portchannel/spc:PORTCHANNEL/spc:PORTCHANNEL_LIST/spc:name";
                    }
                }

                leaf ip_prefix {
                    sonic-ext:custom-validation ValidatePchInterfaceIPAddr;
                    type inet:ip-prefix;
                }

                leaf secondary {
                    type boolean;
                }
            }
        }
    }
}
