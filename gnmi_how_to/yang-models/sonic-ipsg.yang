module sonic-ipsg {
    namespace "http://github.com/Azure/sonic-ipsg";
    prefix sipsg;
    yang-version 1.1;

    import sonic-extension {
        prefix sonic-ext;
    }

    import sonic-port {
        prefix prt;
    }

    import sonic-portchannel {
        prefix spc;
    }

    import sonic-vlan {
        prefix svlan;
    }

    import ietf-inet-types {
        prefix inet;
    }

    import ietf-yang-types {
        prefix yang;
    }

    organization
        "SONiC";

    contact
        "SONiC";

    description
        "SONiC IP Source Guard yang model";

    revision 2021-03-14 {
        description
            "Initial revision.";
    }

    container sonic-ipsg {

        container IPSG_GLOBAL {

            list IPSG_GLOBAL_LIST {

                key "param";
                leaf param {
                    type string {
                        pattern "config";
                    }
                }

                leaf ipv4 {
                    type enumeration {
                        enum enabled;
                        enum disabled;
                    }
                }
            }
        }

        container IPSG_PORT {

            list IPSG_PORT_LIST {

                key "ifname";
                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf ipv4 {
                    type enumeration {
                        enum enabled;
                        enum disabled;
                    }
                }
            }
        }

        container IPSG_PORT_DYNAMIC {

            list IPSG_PORT_DYNAMIC_LIST {

                key "ifname";
                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf ipv4_dhcpsnp {
                    type enumeration {
                        enum enabled;
                        enum disabled;
                    }
                }
            }
        }

        container IPSG_ALLOW {

            list IPSG_ALLOW_LIST {

                key "ifname vlanid ip_address";
                sonic-ext:custom-validation ValidateIPSGrule;
                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf vlanid {
                    type uint16 {
                        range "1..4094" {
                            error-message "Vlan ID out of range";
                            error-app-tag vlanid-invalid;
                        }
                    }
                }

                leaf ip_address {
                    type inet:ipv4-address;
                }

                leaf macaddress {
                    type yang:mac-address;
                }
            }
        }
    }
}
