module sonic-crm {
    namespace "http://github.com/Azure/sonic-crm";
    prefix crm;
    yang-version 1.1;

    import sonic-extension {
        prefix sonic-ext;
    }

    organization
            "SONiC";

    description
            "SONIC CRM";

    revision 2020-04-10 {
        description "First Revision";
    }

    container sonic-crm {

        container CRM {

            description "CRM part of config_db.json";

            /* typedef specific to CRM */
            typedef threshold {
                type uint16;
            }

            typedef crm_threshold_type {
                type string {
                    length 1..64;
                    pattern "percentage|used|free|PERCENTAGE|USED|FREE";
                }
            }

            list CRM_LIST {
                key "name";

                sonic-ext:custom-validation ValidateCRMConfiguration;
                leaf name {
                    type string {
                        pattern "Config"{
                            error-message "Error: Invalid CRM config name";
                        }
                    }
                }

                leaf acl_counter_threshold_type {
                    must "(((current()='PERCENTAGE' or current()='percentage') and
                        ../acl_counter_high_threshold<100 and
                        ../acl_counter_low_threshold<100) or
                        (current()!='PERCENTAGE' and current()!='percentage'))"
                    {
                        error-message "threshold value should be less than 100 with type percentage";
                    }
                    type crm_threshold_type;
                }

                leaf acl_counter_high_threshold {
                    must "(current() > ../acl_counter_low_threshold)"
                    {
                        error-message "high_threshold should be more than low_threshold";
                    }
                    type threshold;
                }

                leaf acl_counter_low_threshold {
                    type threshold;
                }

                leaf acl_group_threshold_type {
                    must "(((current()='PERCENTAGE' or current()='percentage') and
                        ../acl_group_high_threshold<100 and
                        ../acl_group_low_threshold<100) or
                        (current()!='PERCENTAGE' and current()!='percentage'))"
                    {
                        error-message "threshold value should be less than 100 with type percentage";
                    }
                    type crm_threshold_type;
                }

                leaf acl_group_high_threshold {
                    must "(current() > ../acl_group_low_threshold)"
                    {
                        error-message "high_threshold should be more than low_threshold";
                    }
                    type threshold;
                }

                leaf acl_group_low_threshold {
                    type threshold;
                }

                leaf acl_entry_threshold_type {
                    must "(((current()='PERCENTAGE' or current()='percentage') and
                        ../acl_entry_high_threshold<100 and
                        ../acl_entry_low_threshold<100) or
                        (current()!='PERCENTAGE' and current()!='percentage'))"
                    {
                        error-message "threshold value should be less than 100 with type percentage";
                    }
                    type crm_threshold_type;
                }

                leaf acl_entry_high_threshold {
                    must "(current() > ../acl_entry_low_threshold)"
                    {
                        error-message "high_threshold should be more than low_threshold";
                    }
                    type threshold;
                }

                leaf acl_entry_low_threshold {
                    type threshold;
                }

                leaf acl_table_threshold_type {
                    must "(((current()='PERCENTAGE' or current()='percentage') and
                        ../acl_table_high_threshold<100 and
                        ../acl_table_low_threshold<100) or
                        (current()!='PERCENTAGE' and current()!='percentage'))"
                    {
                        error-message "threshold value should be less than 100 with type percentage";
                    }
                    type crm_threshold_type;
                }

                leaf acl_table_high_threshold {
                    must "(current() > ../acl_table_low_threshold)"
                    {
                        error-message "high_threshold should be more than low_threshold";
                    }
                    type threshold;
                }

                leaf acl_table_low_threshold {
                    type threshold;
                }

                leaf fdb_entry_threshold_type {
                    must "(((current()='PERCENTAGE' or current()='percentage') and
                        ../fdb_entry_high_threshold<100 and
                        ../fdb_entry_low_threshold<100) or
                        (current()!='PERCENTAGE' and current()!='percentage'))"
                    {
                        error-message "threshold value should be less than 100 with type percentage";
                    }
                    type crm_threshold_type;
                }

                leaf fdb_entry_high_threshold {
                    must "(current() > ../fdb_entry_low_threshold)"
                    {
                        error-message "high_threshold should be more than low_threshold";
                    }
                    type threshold;
                }

                leaf fdb_entry_low_threshold {
                    type threshold;
                }

                leaf ipv4_neighbor_threshold_type {
                    must "(((current()='PERCENTAGE' or current()='percentage') and
                        ../ipv4_neighbor_high_threshold<100 and
                        ../ipv4_neighbor_low_threshold<100) or
                        (current()!='PERCENTAGE' and current()!='percentage'))"
                    {
                        error-message "threshold value should be less than 100 with type percentage";
                    }
                    type crm_threshold_type;
                }

                leaf ipv4_neighbor_high_threshold {
                    must "(current() > ../ipv4_neighbor_low_threshold)"
                    {
                        error-message "high_threshold should be more than low_threshold";
                    }
                    type threshold;
                }

                leaf ipv4_neighbor_low_threshold {
                    type threshold;
                }

                leaf ipv4_nexthop_threshold_type {
                    must "(((current()='PERCENTAGE' or current()='percentage') and
                        ../ipv4_nexthop_high_threshold<100 and
                        ../ipv4_nexthop_low_threshold<100) or
                        (current()!='PERCENTAGE' and current()!='percentage'))"
                    {
                        error-message "threshold value should be less than 100 with type percentage";
                    }
                    type crm_threshold_type;
                }

                leaf ipv4_nexthop_high_threshold {
                    must "(current() > ../ipv4_nexthop_low_threshold)"
                    {
                        error-message "high_threshold should be more than low_threshold";
                    }
                    type threshold;
                }

                leaf ipv4_nexthop_low_threshold {
                    type threshold;
                }

                leaf ipv4_route_threshold_type {
                    must "(((current()='PERCENTAGE' or current()='percentage') and
                        ../ipv4_route_high_threshold<100 and
                        ../ipv4_route_low_threshold<100) or
                        (current()!='PERCENTAGE' and current()!='percentage'))"
                    {
                        error-message "threshold value should be less than 100 with type percentage";
                    }
                    type crm_threshold_type;
                }

                leaf ipv4_route_high_threshold {
                    must "(current() > ../ipv4_route_low_threshold)"
                    {
                        error-message "high_threshold should be more than low_threshold";
                    }
                    type threshold;
                }

                leaf ipv4_route_low_threshold {
                    type threshold;
                }

                leaf ipv6_neighbor_threshold_type {
                    must "(((current()='PERCENTAGE' or current()='percentage') and
                        ../ipv6_neighbor_high_threshold<100 and
                        ../ipv6_neighbor_low_threshold<100) or
                        (current()!='PERCENTAGE' and current()!='percentage'))"
                    {
                        error-message "threshold value should be less than 100 with type percentage";
                    }
                    type crm_threshold_type;
                }

                leaf ipv6_neighbor_high_threshold {
                    must "(current() > ../ipv6_neighbor_low_threshold)"
                    {
                        error-message "high_threshold should be more than low_threshold";
                    }
                    type threshold;
                }

                leaf ipv6_neighbor_low_threshold {
                    type threshold;
                }

                leaf ipv6_nexthop_threshold_type {
                    must "(((current()='PERCENTAGE' or current()='percentage') and
                        ../ipv6_nexthop_high_threshold<100 and
                        ../ipv6_nexthop_low_threshold<100) or
                        (current()!='PERCENTAGE' and current()!='percentage'))"
                    {
                        error-message "threshold value should be less than 100 with type percentage";
                    }
                    type crm_threshold_type;
                }

                leaf ipv6_nexthop_high_threshold {
                    must "(current() > ../ipv6_nexthop_low_threshold)"
                    {
                        error-message "high_threshold should be more than low_threshold";
                    }
                    type threshold;
                }

                leaf ipv6_nexthop_low_threshold {
                    type threshold;
                }

                leaf ipv6_route_threshold_type {
                    must "(((current()='PERCENTAGE' or current()='percentage') and
                        ../ipv6_route_high_threshold<100 and
                        ../ipv6_route_low_threshold<100) or
                        (current()!='PERCENTAGE' and current()!='percentage'))"
                    {
                        error-message "threshold value should be less than 100 with type percentage";
                    }
                    type crm_threshold_type;
                }

                leaf ipv6_route_high_threshold {
                    must "(current() > ../ipv6_route_low_threshold)"
                    {
                        error-message "high_threshold should be more than low_threshold";
                    }
                    type threshold;
                }

                leaf ipv6_route_low_threshold {
                    type threshold;
                }

                leaf nexthop_group_threshold_type {
                    must "(((current()='PERCENTAGE' or current()='percentage') and
                        ../nexthop_group_high_threshold<100 and
                        ../nexthop_group_low_threshold<100) or
                        (current()!='PERCENTAGE' and current()!='percentage'))"
                    {
                        error-message "threshold value should be less than 100 with type percentage";
                    }
                    type crm_threshold_type;
                }

                leaf nexthop_group_high_threshold {
                    must "(current() > ../nexthop_group_low_threshold)"
                    {
                        error-message "high_threshold should be more than low_threshold";
                    }
                    type threshold;
                }

                leaf nexthop_group_low_threshold {
                    type threshold;
                }

                leaf nexthop_group_member_threshold_type {
                    must "(((current()='PERCENTAGE' or current()='percentage') and
                        ../nexthop_group_member_high_threshold<100 and
                        ../nexthop_group_member_low_threshold<100) or
                        (current()!='PERCENTAGE' and current()!='percentage'))"
                    {
                        error-message "threshold value should be less than 100 with type percentage";
                    }
                    type crm_threshold_type;
                }

                leaf nexthop_group_member_high_threshold {
                    must "(current() > ../nexthop_group_member_low_threshold)"
                    {
                        error-message "high_threshold should be more than low_threshold";
                    }
                    type threshold;
                }

                leaf nexthop_group_member_low_threshold {
                    type threshold;
                }

                leaf polling_interval {
                    type threshold;
                }

                leaf snat_entry_threshold_type {
                    must "(((current()='PERCENTAGE' or current()='percentage') and
                        ../snat_entry_high_threshold<100 and
                        ../snat_entry_low_threshold<100) or
                        (current()!='PERCENTAGE' and current()!='percentage'))"
                    {
                        error-message "threshold value should be less than 100 with type percentage";
                    }
                    type crm_threshold_type;
                }

                leaf snat_entry_high_threshold {
                    must "(current() > ../snat_entry_low_threshold)"
                    {
                        error-message "high_threshold should be more than low_threshold";
                    }
                    type threshold;
                }

                leaf snat_entry_low_threshold {
                    type threshold;
                }

                leaf ipmc_entry_threshold_type {
                    must "(((current()='PERCENTAGE' or current()='percentage') and
                        ../ipmc_entry_high_threshold<100 and
                        ../ipmc_entry_low_threshold<100) or
                        (current()!='PERCENTAGE' and current()!='percentage'))"
                    {
                        error-message "threshold value should be less than 100 with type percentage";
                    }
                    type crm_threshold_type;
                }

                leaf ipmc_entry_high_threshold {
                    must "(current() > ../ipmc_entry_low_threshold)"
                    {
                        error-message "high_threshold should be more than low_threshold";
                    }
                    type threshold;
                }

                leaf ipmc_entry_low_threshold {
                    type threshold;
                }

            }
            /* end of Config */
        }
        /* end of container CRM */
    }
    /* end of top level container */

/* end of module sonic-crm */
}
