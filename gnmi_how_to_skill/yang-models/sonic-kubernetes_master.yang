module sonic-kubernetes_master {

    yang-version 1.1;

    namespace "http://github.com/sonic-net/sonic-kubernetes_master";

    prefix kubernetes_master;

    import ietf-inet-types {
        prefix inet;
    }

    description "KUBERNETES_MASTER YANG Module for SONiC OS";

    revision 2022-10-09 {
        description "First Revision";
    }

    container sonic-kubernetes_master {

        container KUBERNETES_MASTER {

            description "KUBERNETES_MASTER part of config_db.json";

            list KUBERNETES_MASTER_LIST {
                key "param";
                leaf param {
                    type string {
                        pattern "SERVER";
                    }
                }

                leaf ip {
                    description "Kubernetes api server endpoint";
                    type inet:ipv4-address;
                }

                leaf port {
                    description "Kubernetes api server port";
                    type uint16 {
                        range "1..65535";
                    }
                    default 6443;
                }

                leaf disable {
                    description "This configuration identicates whether disable kubernetes";
                    type string {
                        pattern 'False|True';
                    }
                    default "False";
                }

                leaf insecure {
                    description "This configuration identicates it will download kubernetes
                                CA by http other than https";
                    type string {
                        pattern 'false|true|False|True';
                    }
                    default "true";
                }

            }

        }

    }

}
