module sonic-flex-counter {
	yang-version 1.1;
	namespace "http://github.com/Azure/sonic-flex-counter";
	prefix sdm;

	import ietf-yang-types {
		prefix yang;
	}

	import sonic-common {
		prefix scommon;
	}

	import sonic-extension {
		prefix sonic-ext;
	}

	organization
		"SONiC";

	contact
		"SONiC";

	description
		"SONIC DEVICE METADATA";

	revision 2019-07-02 {
		description
			"Initial revision.";
	}

	container sonic-flex-counter {

		container FLEX_COUNTER_TABLE {

			list FLEX_COUNTER_TABLE_LIST {
				key "name";

				leaf name{
					type string;
				}

				leaf FLEX_COUNTER_DELAY_STATUS {
					type boolean;
				}

				leaf FLEX_COUNTER_STATUS {
					type string {
						pattern "enable|disable";
					}
				}

				leaf POLL_INTERVAL {
					type uint32;
					sonic-ext:custom-validation ValidateCounterPollInterval;
				}
			}
		}
	}
}
