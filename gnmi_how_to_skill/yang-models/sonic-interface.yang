module sonic-interface {
	namespace "http://github.com/Azure/sonic-interface";
	prefix sint;

	import ietf-inet-types {
		prefix inet;
	}

	import sonic-port {
		prefix prt;
	}

	import sonic-extension {
		prefix sonic-ext;
	}

	import sonic-vrf {
		prefix vrf;
	}

	organization
		"SONiC";

	contact
		"SONiC";

	description
		"SONIC INTERFACE";

	revision 2019-07-02 {
		description
			"Initial revision.";
	}

	container sonic-interface {

		container INTERFACE {

			list INTERFACE_LIST {
				key "portname";
				sonic-ext:custom-validation ValidateEthernet;

				leaf portname{
					type leafref {
						path "/prt:sonic-port/prt:PORT/prt:PORT_LIST/prt:ifname";
					}
				}

				leaf vrf_name {
					type leafref {
						path "/vrf:sonic-vrf/vrf:VRF/vrf:VRF_LIST/vrf:vrf_name";
					}
				}

				leaf ipv6_use_link_local_only {
					type enumeration {
						enum enable;
						enum disable;
					}
				}

				leaf grat_arp {
					type string {
						pattern "enabled|disabled";
					}
				}

				leaf nat_zone {
					sonic-ext:custom-validation ValidateNatIntf;
					description "NAT Zone for the interface";
					type uint8 {
						range "0..3" {
							error-message "Invalid nat zone for the interface.";
							error-app-tag nat-zone-invalid;
						}
					}
				}

			}

			list INTERFACE_IPADDR_LIST {
				key "portname ip_prefix";

				leaf portname{
					type leafref {
						path "/prt:sonic-port/prt:PORT/prt:PORT_LIST/prt:ifname";
					}
				}

				leaf ip_prefix {
					sonic-ext:custom-validation ValidateEthInterfaceIPAddr;
					type inet:ip-prefix;
				}
				leaf secondary {
					type boolean;
					description "Indicates whether IP adddress configured is secondary or not";
				}
			}
		}

		//change to support in sonic-vlan-sub-interface.yang
		//container VLAN_SUB_INTERFACE {
		//	list VLAN_SUB_INTERFACE_LIST {
		//		key "id";
		//
		//		leaf id {
		//			type string;
		//		}
		//
		//		leaf subintfidx {
		//			type string;
		//		}
		//
		//		leaf ifName {
		//			type string;
		//		}
		//
		//		leaf vrf_name {
		//			type string;
		//		}
		//
		//		leaf vlan {
		//			type string;
		//		}
		//
		//		leaf admin_status {
		//			type string;
		//		}
		//
		//		leaf description {
		//			type string;
		//		}
		//
		//		leaf enabled {
		//			type string;
		//		}
		//
		//		leaf index {
		//			type string;
		//		}
		//
		//	}
		//
		//	list VLAN_SUB_INTERFACE_IPADDR_LIST {
		//		key "id ipPrefix";
		//
		//		leaf id {
		//			type string;
		//		}
		//
		//		leaf ipPrefix {
		//			type inet:ip-prefix;
		//		}
		//
		//		leaf status {
		//			type string;
		//		}
		//	 }
		//}
	}
}
