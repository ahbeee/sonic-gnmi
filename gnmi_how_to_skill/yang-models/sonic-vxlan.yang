module sonic-vxlan {
    namespace "http://github.com/Azure/sonic-vxlan";
    prefix svxlan;
    yang-version 1.1;

    import ietf-yang-types {
        prefix yang;
    }

    import ietf-inet-types {
        prefix inet;
    }

    import sonic-common {
        prefix cmn;
    }

    import sonic-extension {
        prefix sonic-ext;
    }
    import sonic-vlan {
        prefix svlan;
    }

    organization
        "SONiC";

    contact
        "SONiC";

    description
        "SONIC VXLAN";

    revision 2019-10-01 {
        description
            "Initial revision.";
    }

    container sonic-vxlan {

        container VXLAN_TUNNEL {

            list VXLAN_TUNNEL_LIST {
                key "name";
                max-elements 1;

                leaf name {
                    must "(starts-with(../name, 'vtep'))"
                    {
                        error-message "Error: Name should start with vtep";
                        error-app-tag invalid-vtep-name;
                    }
                    type string;
                }

                leaf src_ip {
                    type inet:ipv4-address;
                }
            }
        }

        container VXLAN_TUNNEL_MAP {

            list VXLAN_TUNNEL_MAP_LIST {
                key "name mapname";
                sonic-ext:custom-validation ValidateVxlanMapDelete;

                leaf name {
                    must "(/cmn:operation/cmn:operation != 'CREATE') and (/cmn:operation/cmn:operation != 'UPDATE') or " +
                      "(../../../VXLAN_TUNNEL/VXLAN_TUNNEL_LIST[name=current()]/src_ip != '')"
                    {
                        error-message "Vxlan tunnel map entry cannot be created, since source ip-address does not exist for this tunnel";
                        error-app-tag creation-not-allowed-no-source-ip-exist;
                    }
                    type leafref {
                        path "../../../VXLAN_TUNNEL/VXLAN_TUNNEL_LIST/name";
                    }
                }

                leaf mapname {
                    type string;
                }
                leaf vlan {
                    mandatory true;
                    type leafref {
                        path "/svlan:sonic-vlan/svlan:VLAN/svlan:VLAN_LIST/svlan:name";
                    }

                    sonic-ext:custom-validation ValidateUniqueVlan;
                }

                leaf vni {
                    mandatory true;
                    type uint32 {
                        range "1..16777215" {
                            error-message "Error: VNI ID out of range";
                            error-app-tag vnid-invalid;
                        }
                    }

                    sonic-ext:custom-validation ValidateUniqueVNI;
                }
            }
        }

        container VXLAN_EVPN_NVO {

            list VXLAN_EVPN_NVO_LIST {

                key "name";
                max-elements 1;

                leaf name {
                    type string;
                }

                leaf source_vtep {
                    mandatory true;
                    type leafref {
                        path "../../../VXLAN_TUNNEL/VXLAN_TUNNEL_LIST/name";
                    }
                }
            }
        }

        container SUPPRESS_VLAN_NEIGH {

            list SUPPRESS_VLAN_NEIGH_LIST {
                key "name";

                leaf name {
                    type leafref {
                        path "/svlan:sonic-vlan/svlan:VLAN/svlan:VLAN_LIST/svlan:name";
                    }
                }
                leaf suppress {
                    type enumeration {
                        enum on;
                    }
                }

            }
        }

        container VXLAN_EVPN_ES {

            list VXLAN_EVPN_ES_LIST {
                key "name";
                sonic-ext:custom-validation ValidateVxlanEvpnES;

                leaf name {
                    type string;
                    description "It must be a PortChannel interface";
                }

                leaf es_id  {
                    type string;
                }

                leaf es_sys_mac  {
                    type yang:mac-address;
                }
            }
        }

        container VXLAN_TUNNEL_TABLE {
            sonic-ext:db-name "STATE_DB";
            sonic-ext:key-delim ":";

            config false;
            description "state db vxlan tunnel table";

            list VXLAN_TUNNEL_TABLE_LIST {
                key "name";

                leaf name {
                    type string;
                }
                leaf src_ip {
                    type string;
                }
                leaf dst_ip {
                    type string;
                }
                leaf tnl_src {
                    type string;
                }
                leaf operstatus {
                    type string;
                }
            }
        }

        container VXLAN_REMOTE_VNI_TABLE {
            sonic-ext:db-name "APPL_DB";
            sonic-ext:key-delim ":";

            config false;
            description "app db vxlan remote vni table";

            list VXLAN_REMOTE_VNI_TABLE_LIST {
                key "vlan remote_vtep";

                leaf vlan {
                    type leafref {
                        path "/svlan:sonic-vlan/svlan:VLAN/svlan:VLAN_LIST/svlan:name";
                    }
                }
                leaf remote_vtep {
                    type inet:ipv4-address;
                }
                leaf vni {
                    type string;
                }
            }
        }

        container VXLAN_FDB_TABLE{
            sonic-ext:db-name "APPL_DB";
            sonic-ext:key-delim ":";

            config false;
            description "app db vxlan fdb table";

            list VXLAN_FDB_TABLE_LIST {
                key "vlan mac_addr";

                leaf vlan {
                    type leafref {
                        path "/svlan:sonic-vlan/svlan:VLAN/svlan:VLAN_LIST/svlan:name";
                    }
                }
                leaf mac_addr {
                    type yang:mac-address;
                }
                leaf remote_vtep {
                    type inet:ipv4-address;
                }
                leaf type {
                    type string;
                }
                leaf vni {
                    type string;
                }
            }
        }
    }
}
