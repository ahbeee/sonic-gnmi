module sonic-queue {
	namespace "http://github.com/Azure/sonic-queue";
	prefix squeue;
	yang-version 1.1;

	import sonic-extension {
		prefix sonic-ext;
	}

	import sonic-port {
		prefix prt;
	}

	import sonic-wred-profile {
		prefix wrd;
	}

	import sonic-scheduler {
		prefix sch;
	}

	organization
		"SONiC";

	contact
		"SONiC";

	description
		"SONIC QUEUE";

	revision 2019-05-15 {
		description
			"Initial revision.";
	}


	container sonic-queue {

		container QUEUE {

			list QUEUE_LIST {
				key "ifname qindex";
				sonic-ext:key-pattern "QUEUE|({ifname},)*|{qindex}"; //special pattern used for extracting keys from redis-key and populate the yang instance
										   // Total list instances = number(key1) * number(key2) * number(key3)

				leaf ifname {
					type union {
						type string {
							pattern "CPU";
						}
						type leafref {
							path "/prt:sonic-port/prt:PORT/prt:PORT_LIST/prt:ifname";
						}
					}
				}

				leaf qindex {
					type string;
					sonic-ext:custom-validation ValidateQueueQindex;
				}

				leaf scheduler {
					type leafref {
						path "/sch:sonic-scheduler/sch:SCHEDULER/sch:SCHEDULER_LIST/sch:name"; //Reference to SCHEDULER table
					}
				}

				leaf wred_profile {
					type string;
					sonic-ext:custom-validation ValidateWredProfile;
				}
			}
		}
	}
}
