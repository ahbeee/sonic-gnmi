module sonic-bgp-common {
    namespace "http://github.com/Azure/sonic-bgp-common";
    prefix sbc;
    yang-version 1.1;

    import ietf-inet-types {
        prefix inet;
    }

    import sonic-port {
        prefix prt;
    }

    import sonic-portchannel {
        prefix spc;
    }

    import sonic-vlan {
        prefix svlan;
    }

    import sonic-loopback {
        prefix lo;
    }

    import sonic-routing-policy-sets {
        prefix srpolsets;
    }

    //import sonic-route-map {
    //    prefix srmap;
    //}

    import sonic-common {
        prefix cmn;
    }

    import sonic-extension {
        prefix sonic-ext;
    }

    organization
        "SONiC";

    contact
        "SONiC";

    description
        "SONIC BGP common YANG attributes for Neighbors and Peer group";

    revision 2020-07-26 {
        description
            "Change for sonic-loopback.yang.";
    }
    revision 2019-11-04 {
        description
            "Initial revision.";
    }

    typedef bgp_peer_type {
        type enumeration {
            enum internal {
                description "Internal peer";
            }
            enum external {
                description "External peer";
            }
        }
    }

    typedef bgp_tx_add_paths_type {
      type enumeration {
          enum tx_all_paths {
              description
                  "Send multiple path advertisements for an NLRI from
                  the neighbor or group";
          }
          enum tx_best_path_per_as {
              description
                  "Send only best path per AS advertisements for an NLRI from
                  the neighbor or group";
          }
      }
      description
          "Type to describe the add paths advertisement method.";
    }

    typedef bgp_community_type {
        type enumeration {
            enum standard {
                description "Standard communities";
            }

            enum extended {
                description "Extended communities";
            }

            enum both {
                description "Both standard and extended communities";
            }

            enum large {
                description "Large communities";
            }

            enum all {
                description "Standard, Extended and Large communities";
            }

            enum none {
                description "No community attribute";
            }
        }
        description
            "type describing variations of community attributes";
    }

    typedef sonic_bgp_direction {
        type enumeration {
            enum in {
                description
                    "Refers to information received from the BGP peer";
            }
            enum out {
                description
                    "Refers to information advertised to the BGP peer";
            }
        }
        description
            "Type to describe the direction";
    }

    typedef sonic_bgp_orf {
        type enumeration {
            enum send {
                description
                    "Capability to receive the outbound route filtering from this neighbor";
            }
            enum receive {
                description
                    "Capability to send the outbound route filtering to this neighbor";
            }
            enum both {
                description
                    "Capability to send and receive the outbound route filtering to/from this neighbor";
            }
        }
        description
            "Type to describe the BGP ORF(Outbound route filtering) capability";
    }

    typedef bgp_asn {
        type uint32 {
            range "0..4294967295";
        }
        description
            "The values for as number.
             Note: Set zero to clear the setting";
    }

    grouping sonic-bgp-cmn {

        leaf local_asn {
            type bgp_asn;
            description "Local AS number";
        }

        leaf name {
            type string {
                length "0..80";
            }
            description "Peer description.
            Note: empty string to remove the setting";
        }

        leaf asn {
            type bgp_asn;
            description "Peer AS number";
        }

        leaf peer_type {
            type bgp_peer_type;
        }

        leaf ebgp_multihop {
            type boolean;
            description "EBGP Multihop enabled";
        }

        leaf ebgp_multihop_ttl {
            must "(. >= 1 and . <= 255) or (. <= 0)";
            type int16;
            description "EBGP Multihop TTL";
        }

        leaf auth_password {
            type string {
                length "0..16";
            }
            description "Authuntiation password.
            Note: empty string to remove the setting";
        }

        leaf keepalive {
            type uint16;
            description "Keepalive interval";
        }

        leaf holdtime {
            type uint16;
            description "Hold time";
        }

        leaf conn_retry {
            must "(. >= 1 and . <= 65535) or (. <= 0)";
            type int32;
            description "Connection retry time";
        }

        leaf min_adv_interval {
            must "(. >= 0 and . <= 600) or (. < 0)";
            type int16;
            description "minium advertisement interval";
        }

        leaf local_addr {
            type union {
                type inet:ip-address;
                type leafref {
                    path "/prt:sonic-port/prt:PORT/prt:PORT_LIST/prt:ifname";
                }
                type leafref {
                    path "/spc:sonic-portchannel/spc:PORTCHANNEL/spc:PORTCHANNEL_LIST/spc:name";
                }
                type leafref {
                    path "/svlan:sonic-vlan/svlan:VLAN/svlan:VLAN_LIST/svlan:name";
                }
            }
            description "Local source address or interface name to use for connection.";
        }

        leaf passive_mode {
            type boolean;
            description "Passive mode";
        }

        leaf capability_ext_nexthop {
            type boolean;
            description "Advertise extended nexthop capability";
        }

        leaf disable_ebgp_connected_route_check {
            type boolean;
            description "Connected checked disabled";
        }

        leaf enforce_first_as {
            type boolean;
            description "Enforce first AS for EBGP";
        }

        leaf solo_peer {
            type boolean;
            description "Part of own update group";
        }

        leaf ttl_security_hops {
            must "(. >= 1 and . <= 254) or (. <= 0)";
            type int16;
            must "((current() = 1 and (starts-with(current()/../neighbor, 'Ethernet') or starts-with(current()/../neighbor, 'PortChannel') or starts-with(current()/../neighbor, 'Vlan'))) or (not(starts-with(current()/../neighbor, 'Ethernet') or starts-with(current()/../neighbor, 'PortChannel') or starts-with(current()/../neighbor, 'Vlan'))))" {
                error-message "Hops for connected neighbor cannot exceed 1";
            }
            description "TTL";
        }

        leaf bfd {
            type boolean;
            description "BFD status";
        }

        leaf bfd_check_ctrl_plane_failure {
            type boolean;
            description "Link dataplane status with BGP control plane";
        }

        leaf capability_dynamic {
            type boolean;
            description "Advertise dynamic capability";
        }

        leaf dont_negotiate_capability {
            type boolean;
            description "Do not perform capability negotiation";
        }

        leaf enforce_multihop {
            type boolean;
            description "Enforce EBGP neighbors perform multihop";
        }

        leaf override_capability {
            must "not(../strict_capability_match='true' and .='true')" {
                error-message "Can't set override-capability and strict-capability-match at the same time";
            }
            type boolean;
            description "Override capability negotiation result";
        }

        leaf peer_port {
            type uint16;
            description "Peer port number";
        }

        leaf shutdown_message {
            type string {
                length "0..128";
            }
            description "Message on peer/Neighbor shutdown.
            Note: empty string to remove the setting";
        }

        leaf strict_capability_match {
            must "not(../override_capability='true' and .='true')" {
                error-message "Can't set override-capability and strict-capability-match at the same time";
            }
            type boolean;
            description "Strict capability negotiation match";
        }

        leaf admin_status {
            type boolean;
            description "To enable BGP peer";
        }

        leaf local_as_no_prepend {
            type boolean;
            description "Do not prepend local-as to updates from ebgp peers";
        }

        leaf local_as_replace_as {
            type boolean;
            description "Do not prepend local-as to updates from ibgp peers";
        }
    }


    grouping sonic-bgp-cmn-af {

        leaf afi_safi {
            type string;
            description "Address family";
        }

        leaf admin_status {
            type boolean;
            description "Enabled status";
        }

        leaf send_default_route {
            type boolean;
            description "Send default route";
        }

        leaf default_rmap {
            type string;

            /* Not support route-map yang yet
            type leafref {
                path "/srmap:sonic-route-map/srmap:ROUTE_MAP_SET/srmap:ROUTE_MAP_SET_LIST/srmap:name";
            }
            */
            description "Default route map to originate";
        }

        leaf max_prefix_limit {
            type uint32;
            description "Maximum prefix limit
            Note: Set zero to remove the setting";
        }

        leaf max_prefix_warning_only {
            type boolean;
            description "On maximum prefix limit, warn only";
        }

        leaf max_prefix_warning_threshold {
            type uint8 {
                range "0..100";
            }
            description "Maximum prefix limit threshold for warning
            Note: Set zero to remove the setting";
        }

        leaf max_prefix_restart_interval {
            type uint16 {
                range "0..65535";
            }
            description "Interval after which connection will get re-established
            Note: Set zero to remove the setting";
        }

        leaf route_map_in {
            type string;

            /* Not support route-map yang yet
            type leafref {
                path "/srmap:sonic-route-map/srmap:ROUTE_MAP_SET/srmap:ROUTE_MAP_SET_LIST/srmap:name";
            }
            */
        }

        leaf route_map_out {
            type string;

            /* Not support route-map yang yet
            type leafref {
                path "/srmap:sonic-route-map/srmap:ROUTE_MAP_SET/srmap:ROUTE_MAP_SET_LIST/srmap:name";
            }
            */
        }

        leaf soft_reconfiguration_in {
            type boolean;
            description "Inbound soft reconfiguration";
        }

        leaf unsuppress_map_name {
            type string;

            /* Not support route-map yang yet
            type leafref {
                path "/srmap:sonic-route-map/srmap:ROUTE_MAP_SET/srmap:ROUTE_MAP_SET_LIST/srmap:name";
            }
            */
            description "Route map";
        }

        leaf route_reflector_client {
            type boolean;
            description "Route reflector client";
            sonic-ext:custom-validation ValidateRouteReflectorClient;
        }

        leaf weight {
            type uint16 {
                range 0..65535;
            }
        }

        leaf as_override {
            type boolean;
        }

        leaf send_community {
            type bgp_community_type;
        }

        leaf tx_add_paths {
            type bgp_tx_add_paths_type;
            description "Advertise all paths or best path per AS using add path";
        }

        leaf unchanged_as_path {
            type boolean;
            description "AS path attribute unchanged";
        }

        leaf unchanged_med{
            type boolean;
            description "MED attribute unchanged";
        }

        leaf unchanged_nexthop {
            type boolean;
            description "nexthop attribute unchanged";
        }

        leaf filter_list_in {
            type leafref {
                path "/srpolsets:sonic-routing-policy-sets/srpolsets:AS_PATH_SET/srpolsets:AS_PATH_SET_LIST/srpolsets:name";
            }
            description "Filter list name";
        }

        leaf filter_list_out {
            type leafref {
                path "/srpolsets:sonic-routing-policy-sets/srpolsets:AS_PATH_SET/srpolsets:AS_PATH_SET_LIST/srpolsets:name";
            }
            description "Filter list name";
        }

        leaf nhself {
            type boolean;
            description "Nexthop is self, no nexthop calculation";
        }

        leaf nexthop_self_force {
            type boolean;
            description "Force nexthop to be self for reflected routes";
        }

        leaf prefix_list_in {
            type leafref {
                path "/srpolsets:sonic-routing-policy-sets/srpolsets:PREFIX_SET/srpolsets:PREFIX_SET_LIST/srpolsets:name";
            }
            description "Prefix list name";
        }

        leaf prefix_list_out {
            type leafref {
                path "/srpolsets:sonic-routing-policy-sets/srpolsets:PREFIX_SET/srpolsets:PREFIX_SET_LIST/srpolsets:name";
            }
            description "Prefix list name";
        }

        leaf remove_private_as_enabled {
            type boolean;
            description "Remove private ASN's in outbound updates";
        }

        leaf replace_private_as {
            type boolean;
            description "Replace private ASN's with our ASN in outbound updates";
        }

        leaf remove_private_as_all {
            type boolean;
            description "Remove all ASN's in outbound updates";
        }

        leaf allow_as_in {
            type boolean;
            description "Allow own ASN in AS path";
        }

        leaf allow_as_count {
            type uint8;
            description "Number of occurances of ASN";
        }

        leaf allow_as_origin {
            type boolean;
            description "Allow own AS in AS path, if route originated in own AS";
        }

        leaf cap_orf {
            type sonic_bgp_orf;
            description "ORF(Outbound Route Filtering) capability";
        }

        leaf route_server_client {
            type boolean;
            description "Route server client";
        }
    }

    grouping sonic-bgp-evpn-vni-common {

        leaf advertise-default-gw {
            type boolean;
        }

        leaf advertise-svi-ip {
            type boolean;
        }

        leaf route-distinguisher {
            type string;
        }

        leaf-list import-rts {
            type string;
        }

        leaf-list export-rts {
            type string;
        }

    }

    grouping sonic-bgp-af-evpn-global {

        uses sonic-bgp-evpn-vni-common;

        leaf advertise-all-vni {
            must "current()/../vrf_name = 'default'" {
                error-message "Advertise all VNI is only supported on default VRF!";
            }
            type boolean;
        }

        leaf advertise-ipv4-unicast {
            type boolean;
        }

        leaf advertise-ipv6-unicast {
            type boolean;
        }

        leaf default-originate-ipv4 {
            type boolean;
        }

        leaf default-originate-ipv6 {
            type boolean;
        }

        leaf autort {
            type string;
        }

        /*leaf flooding {
            type string;
        }*/

        leaf dad-enabled {
            must "((../advertise-all-vni='true') or (current()='false'))" {
                error-message "This command is only supported under the EVPN VRF";
            }
            type boolean;
        }

        leaf dad-max-moves {
            type uint32;
        }

        leaf dad-time {
            type uint32;
        }

        leaf dad-freeze {
            type string;
        }

    }

}
