module sonic-dscp-tc-map {
    namespace "http://github.com/Azure/sonic-dscp-tc-map";
    prefix dtm;

    import sonic-extension {
        prefix sonic-ext;
    }

    organization
        "SONiC";

    contact
        "SONiC";

    description
        "SONIC DSCP_TO_TC_MAP";

    revision 2019-05-15 {
        description
            "Initial revision.";
    }

    container sonic-dscp-tc-map {

        container DSCP_TO_TC_MAP {

            list DSCP_TO_TC_MAP_LIST {
                key "name";
                sonic-ext:map-list true; //special conversion for map tables
                sonic-ext:map-leaf "dscp tc_num"; //every key:value pair is mapped to list keys, e.g. "1":"7" ==> tc_num=1, dscp=7
                sonic-ext:custom-validation ValidateDscptoTc;

                leaf name {
                    type string;
                }

                list DSCP_TO_TC_MAP_INTERNAL_LIST { //this is list inside list for storing mapping between two fields
                    key "dscp tc_num";

                    leaf dscp {
                        type string;
                    }

                    leaf tc_num {
                        type string;
                    }
                }
            }
        }
    }
}
