module sonic-lldp {
    namespace "http://github.com/Azure/sonic-lldp";
    prefix lldp;
    yang-version 1.1;

    import sonic-port {
        prefix prt;
    }

    import ietf-inet-types {
        prefix inet;
    }

    organization
        "SONiC";

    contact
        "SONiC";

    description
        "SONIC LLDP";

    revision 2021-07-15 {
        description
            "Initial revision.";
    }

    grouping lldp_mode_config {
        leaf enabled {
            type boolean;
            default true;
            description
                "Enable/Disable LLDP";
        }

        leaf mode {
            type enumeration {
                enum RECEIVE;
                enum TRANSMIT;
            }

            description
                "RX/TX mode for LLDP frames";
        }
    }

    container sonic-lldp {

        container LLDP {

            container GLOBAL {

                leaf hello_time {
                    type uint16 {
                        range "5..65534" {
                            error-message "Hello timer out of range";
                            error-app-tag LLDP_HelloTimer-invalid;
                        }
                    }
                }

                leaf mgmt_ip {
                    type inet:ip-address;
                }

                leaf system_description {
                    type string;
                }

                leaf system_name {
                    type string;
                }

                leaf med_policy {
                    type string;
                }
            }
        }

        container LLDP_PORT {
            list LLDP_PORT_LIST {
                key "ifname";

                leaf ifname {
                    type leafref {
                        path "/prt:sonic-port/prt:PORT/prt:PORT_LIST/prt:ifname";
                    }
                    description
                        "Reference of port on which LLDP to be configured.";
                }

                uses lldp_mode_config;
            }
        }

        container LLDP_INTERFACE {

            list LLDP_INTERFACE_LIST {
                key "ifname";

                leaf ifname{
                    type union {
                        type leafref {
                            path "/prt:sonic-port/prt:PORT/prt:PORT_LIST/prt:ifname";
                        }
                        type string {
                            pattern "eth([1-3][0-9]{3}|[1-9][0-9]{2}|[1-9][0-9]|[0-9])"{
                                error-message "Invalid Management interface name";
                                error-app-tag mgmt-interface-name-invalid;
                            }
                        }
                    }
                }

                leaf med_location {
                    type string;
                }

                leaf med_policy {
                    type string;
                }

                leaf dcbx_pfc {
                    type string {
                        pattern "enable|disable";
                    }
                    default "disable";
                }

                leaf dcbx_ets_cfg {
                    type string {
                        pattern "enable|disable";
                    }
                    default "disable";
                }

                leaf dcbx_ets_rec {
                    type string {
                        pattern "enable|disable";
                    }
                    default "disable";
                }
            }
        }
    }
}
