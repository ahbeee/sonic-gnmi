module sonic-loopback-interface {
    namespace "http://github.com/Azure/sonic-loopback-interface";
    prefix sonic-lo-if;

    import ietf-inet-types {
        prefix inet;
    }

   import sonic-vrf {
        prefix vrf;
    }

    import sonic-extension {
        prefix sonic-ext;
    }

    organization
        "SONiC";

    contact
        "SONiC";

    description
        "SONIC LOOPBACK INTERFACE";

    revision 2019-07-02 {
        description
            "Initial revision.";
    }

    revision 2019-12-01 {
        description
            "Add vrf_name for VRF interface binding.";
    }

    container sonic-loopback-interface {

        container LOOPBACK_INTERFACE {

            list LOOPBACK_INTERFACE_LIST {
                key "loIfName";

                leaf loIfName{
                    type string {
                            pattern "Loopback([0-9]|[1-8][0-9]|9[0-9]|[1-8][0-9]{2}|" +
                                    "9[0-8][0-9]|99[0-9]|[1-8][0-9]{3}|9[0-8][0-9]{2}|" +
                                    "99[0-8][0-9]|999[0-9]|1[0-5][0-9]{3}|16[0-2][0-9]{2}|163[0-7][0-9]|1638[0-3])";
                   }
                }

                leaf nat_zone {
                    sonic-ext:custom-validation ValidateNatIntf;
                    description "NAT Zone for the loopback interface";
                    type uint8 {
                        range "0..3" {
                            error-message "Invalid nat zone for the loopback interface.";
                            error-app-tag nat-zone-invalid;
                        }
                    }
                }

                leaf vrf_name {
                    type leafref {
                        path "/vrf:sonic-vrf/vrf:VRF/vrf:VRF_LIST/vrf:vrf_name";
                    }
                }

                leaf description {
                    type string {
                        pattern '[ -~]{0,64}';
                    }
                }
            }

            list LOOPBACK_INTERFACE_IPADDR_LIST {
                key "loIfName ip_prefix";

                leaf loIfName{
                    type string;
                }

                leaf ip_prefix {
                    type inet:ip-prefix;

                }
                leaf secondary {
                    type boolean;
                }
            }
        }
    }
}
