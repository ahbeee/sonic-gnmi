module sonic-vlan {
    namespace "http://github.com/Azure/sonic-vlan";
    prefix svlan;
    yang-version 1.1;

    import sonic-extension {
        prefix sonic-ext;
    }

    import sonic-common {
        prefix scommon;
    }

    import sonic-port {
        prefix prt;
    }

    import sonic-portchannel {
        prefix spc;
    }

    import sonic-loopback-interface {
        prefix sonic-lo-if;
    }

    import ietf-inet-types {
        prefix inet;
    }

    import sonic-interface {
        prefix sint;
    }

    import sonic-mirror {
        prefix smir;
    }
    organization
        "SONiC";

    contact
        "SONiC";

    description
        "SONIC VLAN";

    revision 2019-05-15 {
        description
            "Initial revision.";
    }


    container sonic-vlan {

        container VLAN {

            list VLAN_LIST {
                key "name";
                sonic-ext:custom-validation ValidateVlanVID;
                must "./name = concat('Vlan', string(./vlanid))"{
                    error-app-tag vlan-invalid;
                }

                leaf name {
                    type string {
                        pattern "Vlan(409[0-4]|40[0-8][0-9]|[1-3][0-9]{3}|[1-9][0-9]{2}|[1-9][0-9]|[1-9])" {
                            error-message "Invalid Vlan name pattern";
                            error-app-tag vlan-name-invalid;
                        }
                    }
                }

                leaf vlanid {
                    mandatory true;
                    type uint16 {
                        range "1..4094" {
                            error-message "Vlan ID out of range";
                            error-app-tag vlanid-invalid;
                        }
                    }
                }

                leaf-list members {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                }

                leaf-list dhcp_servers {
                    type inet:ip-address;
                }

                leaf-list dhcpv6_servers {
                    type inet:ipv6-address;
                }

                leaf mtu  {
                    type uint32 {
                        range "1312..9216" {
                            error-message "Invalid MTU value";
                            error-app-tag mtu-invalid;
                        }
                    }
                }

                leaf admin_status {
                    type scommon:admin-status;
                }

                leaf description {
                    type string {
                        length 1..255;
                    }
                }

                leaf dhcp_relay_link_selection {
                    sonic-ext:custom-validation ValidateDHCPRelayLinkSelection;
                    type string {
                        pattern "enabled" {
                            error-message "Invalid link selection pattern";
                            error-app-tag link-selection-invalid;
                        }
                    }
                }

                leaf dhcp_relay_src_intf {
                    sonic-ext:custom-validation ValidateDHCPRelaySourceIntf;
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                        type string {
                            pattern "Vlan(409[0-4]|40[0-8][0-9]|[1-3][0-9]{3}|[1-9][0-9]{2}|[1-9][0-9]|[1-9])" {
                                error-message "Invalid Vlan name pattern";
                                error-app-tag vlan-name-invalid;
                            }
                        }
                        type leafref {
                            path "/sonic-lo-if:sonic-loopback-interface/sonic-lo-if:LOOPBACK_INTERFACE/sonic-lo-if:LOOPBACK_INTERFACE_LIST/sonic-lo-if:loIfName";
                        }
                    }
                }

                leaf dhcp_relay_server_vrf {
                    sonic-ext:custom-validation ValidateDHCPRelayServerVRF;
                    type string;
                }

                leaf dhcp_relay_server_override {
                    type string {
                        pattern "enabled" {
                            error-message "Invalid server override pattern";
                            error-app-tag server-override-invalid;
                        }
                    }
                }

                leaf dhcp_relay_primary_address {
                    type inet:ip-address;
                }

                leaf dhcp_relay_max_packet_size  {
                    type uint32 {
                        range "576..1500" {
                            error-message "Max packet size should be between 576 and 1500";
                            error-app-tag dhcp-relay-max-packet-size-invalid;
                        }
                    }
                }
                leaf dhcp_suppress {
                    type boolean;
                    default false;
                }
            }
        }

        container VLAN_MEMBER {

            list VLAN_MEMBER_LIST {
                key "name ifname";

                leaf name {
                    type leafref {
                        path "../../../VLAN/VLAN_LIST/name";
                    }
                }

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
					must "not(/smir:sonic-mirror/smir:MIRROR_SESSION/smir:MIRROR_SESSION_LIST[smir:dst_port=current()])"
					{
						error-message "Port is used as a destination port in a mirror session.";
					}
					must "count(../../svlan:VLAN_MEMBER_LIST[svlan:ifname=current() and svlan:tagging_mode='untagged']) <= 1" {
						error-message "Port can be untagged in at most one VLAN.";
					}
                }
                sonic-ext:custom-validation ValidateVlanMember;

                leaf tagging_mode {
                    type scommon:tagging_mode;
                    default tagged;
                }
            }
        }

        container VLAN_TABLE {
            config false;

            list VLAN_TABLE_LIST {
                key "name";
                must "./name = concat('Vlan', string(./vlanid))" {
                    error-app-tag vlan-invalid;
                }

                leaf name {
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                }

                leaf admin_status {
                    type scommon:admin-status;
                }

                leaf mtu {
                    type uint32 {
                        range "1312..9216" {
                            error-message "Invalid MTU value";
                            error-app-tag mtu-invalid;
                        }
                    }
                }

                leaf oper_status {
                    type scommon:oper-status;
                }
            }
        }

        container VLAN_MEMBER_TABLE {
            config false;

            list VLAN_MEMBER_TABLE_LIST {
                key "name ifname";

                leaf name {
                    type leafref {
                        path "../../../VLAN_TABLE/VLAN_TABLE_LIST/name";
                    }
                }

                leaf ifname {
                    type leafref {
                        path "/prt:sonic-port/prt:PORT/prt:PORT_LIST/prt:ifname";
                    }
                }

                leaf tagging_mode {
                    type scommon:tagging_mode;
                }
            }
        }

        container VLAN_RANGE_MEMBER {

            list VLAN_RANGE_MEMBER_LIST {
                key "ifname";

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    sonic-ext:custom-validation ValidateVlanRangeMember;
                }

                leaf tagging_mode {
                    type scommon:tagging_mode;
                    default tagged;
                }

                leaf ranges {
                    type string;
                }

                leaf operation {
                    type string;
                }
            }
        }

        container VLAN_RANGE {

            list VLAN_RANGE_LIST {
                key "ranges";

                leaf ranges {
                    type string;
                }

                leaf operation {
                    type string;
                }
            }
        }
    }
}
