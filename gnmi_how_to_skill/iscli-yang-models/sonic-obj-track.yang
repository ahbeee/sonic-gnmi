module sonic-obj-track {

    yang-version 1.1;

    namespace "http://github.com/Azure/sonic-obj-track";
    prefix objtrk;

    import ietf-inet-types {
        prefix inet;
    }

    import sonic-port {
        prefix port;
    }

    import sonic-portchannel {
        prefix lag;
    }

    description "Object Track yang Module for SONiC OS";

    revision 2023-04-17 {
        description "First Revision";
    }

    container sonic-obj-track {
        container OBJ_TRACK {
            description "OBJ_TRACK part of config_db.json";

            list OBJ_TRACK_LIST {

                max-elements 30;

                key "session_name";

                leaf session_name {
                    description
                        "The configuration of the obj-track session name";
                    type string {
                        pattern '[a-zA-Z0-9]{1}([-a-zA-Z0-9_]{0,31})' {
                            error-message "Invalid object track session name.";
                            error-app-tag obj-track-invalid-session-name;
                        }
                        length 1..32 {
                            error-message "Invalid length for the object track session name.";
                            error-app-tag obj-track-invalid-session-name-length;
                        }
                    }
                }

                leaf-list tracked_port_list {
                    description
                        "A list which contains the tracked ports or port channels. For example, 'Ethernet0,Ethernet1,PortChannel1'";
                    type union {
                        type leafref {
                            path "/port:sonic-port/port:PORT/port:PORT_LIST/port:name";
                        }
                        type leafref {
                            path "/lag:sonic-portchannel/lag:PORTCHANNEL/lag:PORTCHANNEL_LIST/lag:name";
                        }
                        // Allow an empty string
                        type string {
                            length "0"; // Specifically allows an empty string
                        }
                    }
                }

                leaf-list tracked_bgp_nbr_list {
                    description
                        "A list which contains the tracked BGP neighbors. For example, 'Ethernet0,PortChannel1,192.168.1.1,fc00::6e'";
                    type union {
                        type inet:ip-address;
                        type leafref {
                            path "/port:sonic-port/port:PORT/port:PORT_LIST/port:name";
                        }
                        type leafref {
                            path "/lag:sonic-portchannel/lag:PORTCHANNEL/lag:PORTCHANNEL_LIST/lag:name";
                        }
                        // Allow an empty string
                        type string {
                            length "0"; // Specifically allows an empty string
                        }
                    }
                }

                leaf-list tracked_vxlan_tunnel_list {
                    description
                        "A list which contains the tracked Vxlan tunnels. For example, '1.1.1.2,1.1.1.3'";
                    type union {
                        type inet:ip-address;
                        // Allow an empty string
                        type string {
                            length "0"; // Specifically allows an empty string
                        }
                    }
                }

                leaf-list downlink_interface_list {
                    description
                        "A list which contains the downlink interfaces. For example, 'Ethernet4,Ethernet5,PortChannel2'";
                    type union {
                        type leafref {
                            path "/port:sonic-port/port:PORT/port:PORT_LIST/port:name";
                        }
                        type leafref {
                            path "/lag:sonic-portchannel/lag:PORTCHANNEL/lag:PORTCHANNEL_LIST/lag:name";
                        }
                        // Allow an empty string
                        type string {
                            length "0"; // Specifically allows an empty string
                        }
                    }
                }

                leaf guard_time {
                    description "The guard time of specific obj-track session";
                    type uint16 {
                        range "0..300" {
                            error-message "Invalid guard time for object track.";
                            error-app-tag obj-track-invalid-guard-time-value;
                        }
                    }
                    default "60";
                }

                leaf auto_recovery {
                    description "Enable or disable auto-recovery for this session";
                    type string {
                        pattern "enabled|disabled" {
                            error-message "Invalid auto-recovery state for object track session.";
                            error-app-tag obj-track-invalid-auto-recovery-state;
                        }
                    }
                    default "enabled";
                }

                leaf state {
                    description "The port track session admin status";
                    type string {
                        pattern "enabled|disabled" {
                            error-message "Invalid admin state for object track session.";
                            error-app-tag obj-track-invalid-session-admin-state;
                        }
                    }
                }
            }
        }
    }

} /* end of module sonic-obj-track */
