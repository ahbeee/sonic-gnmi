module sonic-vrf {
    namespace "http://github.com/sonic-net/sonic-vrf";
    prefix vrf;

    import sonic-extension {
        prefix sonic-ext;
    }

    organization
        "SONiC";

    contact
        "SONiC";

    description
        "SONIC VRF";

    revision 2021-03-30 {
        description
            "Initial revision.";
    }

    container sonic-vrf {
        container VRF {
            description "Vrf configuration.";

            list VRF_LIST {
                key "name";

                leaf name {
                    type string {
                        pattern "Vrf[a-zA-Z0-9_-]+" {
                            error-message "Invalid VRF name";
                            error-app-tag vrf-name-invalid;
                        }
                    }
                }

                leaf fallback {
                    type  boolean;
                    default false;
                    description
                        "Enable/disable fallback feature which is useful for specified VRF user to access internet through global/main route.";
                }

                leaf vni {
                    type uint32 {
                        range "1..16777215";
                    }
                    default 1;
                    description
                        "VNI mapped to VRF";
                }

                leaf enable_link_local {
                    type string {
                        pattern "enable|disable";
                    }
                }
            } /* end of list VRF_LISt */
        } /* end of container VRf */
    } /* end of container sonic-vrf */
}/* end of module sonic-vrf */
